module dhcp {
     namespace "http://example.com/ns/dhcp";
     prefix dhcp;

     import ietf-yang-types { prefix yang; }
     import ietf-inet-types { prefix ineti; }






     organization
       "yang-central.org";
     description
       "Partial data model for DHCP, based on the config of
        the ISC DHCP reference implementation.";



     container dhcp {
       description
         "configuration and operational parameters for a DHCP server.";
         
         //config true;
         
         must  "max-lease < 3" {error-message "Tres gross Error";
         error-app-tag "TGE";}

       leaf max-lease-time {
         type uint32 { range 4..8000|8003..8006;}
         units seconds;
         default 7200;
       }
       
       typedef dozen { type uint8 { range 1..12;} default 7;}
       leaf mounth { type dozen {range 7..12;} default 8; }
       
       typedef test { type ineti:ip-prefix; default "0.0.0.0/5";}
       
       
       leaf ref { type leafref { path ../max-lease-time;}}
       leaf con { type test; default "1.1.1.1/6";}
       
       leaf tfloat { type decimal64 {fraction-digits 5;}}
       
       choice ch {
         //default c;
         mandatory true;
         case a {leaf a{type int8;}leaf aa {type int8;}}
         leaf c {type int8;}
        }


	anyxml configName ;
	
       leaf default-lease-time {
         type uint32;
         units seconds;
         must '. <= ../max-lease-time' {
           error-message
             "The default-lease-time must be less than max-lease-time";
         }
         
         default 600;
       }

       uses subnet-list;

       container shared-networks {
         list shared-network {
           key name;
           //min-elements 2;
           max-elements 14;
           
           unique "name c/name";

           leaf name {
             type string;
           }
           
           container c {
             leaf name {
               type string;
           }
            
           }
           uses subnet-list;
         }
       }

       container status {
         config false;
         list leases {
           key address;


           leaf address {
             type ineti:ip-address;
           }
           leaf starts {
             type yang:date-and-time;
           }
           leaf ends {
             type yang:date-and-time;
           }
           container hardware {
             leaf type {
               type enumeration {
                 enum "ethernet";
                 enum "token-ring";
                 enum "fddi";
               }
             }
             leaf address {
               type yang:phys-address;
             }
           }
         }
       }
     }
     
	
     grouping subnet-list {
       description "A reusable list of subnets";
       list subnet {
         must "dhcp/max-lease-time < 12";
         key net;
         
         unique "net range/low dhcp-options/domain-name";
         leaf net {
           type ineti:ip-prefix;
         }
         container range {
           presence "enables dynamic address assignment";
           leaf dynamic-bootp {
             type empty;
             description
               "Allows BOOTP clients to get addresses in this range";
           }

           leaf low {
             type ineti:ip-address;
             mandatory true;
           }
           leaf high {
             type ineti:ip-address;
             mandatory true;
           }
         }

         container dhcp-options {
           description "Options in the DHCP protocol";
           leaf-list router {
             type ineti:host;
             ordered-by user;
             reference "RFC 2132, sec. 3.8";
           }
           leaf domain-name {
             type ineti:domain-name;
             reference "RFC 2132, sec. 3.17";
           }
         }

         leaf max-lease-time {
           type uint32;
           units seconds;
           default 7200;
         }
       }
     }
   }
