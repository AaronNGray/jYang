module example1 {
       namespace "http://example.com/ns/example1";
       prefix ex1;
       import "ietf-inet-types" {
           prefix "inet";
       }
       
       typedef vowels {
           type string {
               pattern "[aeiouy]*";
           }
       }
       
       
       grouping "grp1" {
           leaf
           "void" {
           	
           	type "empty";
           }
           
          }
          
          container "cont" {
          	
          	grouping "grp2" {
          		
          		leaf "address" {
          			
          			type "inet:ip-address";
          		}
          		
          		container r {
          			
          			typedef toto {
          				type int8;
          			}
          			
          		}
          		
          	}
          	
          	leaf foo {
          		
          		type vowels;
          	}
          	
          	uses "grp1";
           uses "grp2";
       }
   }
