submodule ipif {
  belongs-to module {
    prefix "Module";
  }

  include pool;

  extension substatement {
    argument name;
  }


  extension action {
    argument name;
    Module:substatement "input";
    Module:substatement "output";
  }


  grouping IpIf-Mos {

          list IpIf {
            max-elements 16383;
            key "rdnId";
            leaf rdnId {
              mandatory true;
              type uint16 {
                range "1..16383";
              }
            }

        Module:action switchOver {
 
         input {
//             leaf a {}
          }
          output {
//              leaf b {}

          }
        }


            uses BwPool-Mos;
      }
   }
}
