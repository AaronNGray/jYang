module example2 {
	
	namespace "http://example.com/ns/example2";
	prefix ex2;
	grouping leaves {
		
		uses fr;
		uses es;
		container en {
		   leaf leaf {
			type string;
			}
		}
	}
	
	grouping fr {
		
		leaf feuille {
			
			type string;
		}
		
	}
	grouping en {
		
		leaf leaf {
			
			type string;
		}
		
	}
	
	grouping es {
		
		leaf hoja {
			
			type string;
		}
		
	}
	  
	uses leaves {
		refine "hoja" {
			default "alamo";
		}
		refine en/leaf { default "toto";}
	}
	
}
