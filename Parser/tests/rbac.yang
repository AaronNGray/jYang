submodule rbac {
	
	belongs-to netconf { prefix rabc;}
	
	
 	typedef user_id {
 		type int16 {
 			range "1..max";
 		}
 	}
 	
 	
 	typedef name {
 		type string {
 			length "3..30";
 			pattern "([A-Z][a-z| ])*";
 		}
 	}
 	typedef login {
 		type string {
 			length "3..8";
 			pattern "[a-z]*";
 		}
 	}
 	typedef user_password {
 		type string {
 			length "8..25";
 		}
 	}
 	
 	typedef public_key {
 		type string;
 	}
 	typedef user_room {
 		type string;
 	}
 	
 	grouping user_localization {
 		leaf firstname { type name;}
 		leaf lastname { type name;}
 		leaf room {type user_room;}
 		leaf publickey {type public_key;} 
 	}
 	
 	grouping rbac {
 		container rbac {
 		container users {
 		list user {
 			key "id";
 		
 			leaf id {type user_id;}
 			leaf login { type login;}
 			leaf password { type user_password;}
 			choice  c {
 				case user_localization{
 					uses user_localization;
 				}
 				case nolocation {
 					leaf nolocation {
 						type empty;
 					}
 				}
 			}
 		}
 		}
 	 }
 	}
 	
 	
 	typedef role_id {
 		type int16 {
 			range "1..max";
 		}
 	}
 	
 	typedef junior_role {
 		type role_id;
 	}
 	
 	list roles {
 		key "id";
 		
 		choice c {
 		   case root {
 		 	 leaf id { type role_id;}
 		   }
 		   case junior {
 		 	  leaf id2 { type role_id;}
 		 	  leaf-list juniors {
 		 	        type junior_role;
 		 	   }
 		 	}
 		}
 	}
 	
 	container monContainer {
 		uses rbac;
 		//container rbac{}
 		//uses rbac;
 	}
 	
 	//container monContainer {
 	//}
 	
 	//uses rbac;
 	uses rbac;
 		
 		
 		choice CC {
 			case a {
 				uses rbac;
 				leaf l3{ type int8;}
 			}
 			case b {
 				//uses rbac;
 				leaf l1 {type int8;}
 				leaf l2 { type int8;}
 			}
 		}

}
