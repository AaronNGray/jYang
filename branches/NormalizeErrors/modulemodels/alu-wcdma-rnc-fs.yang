submodule alu-wcdma-rnc-fs {

   belongs-to alu-wcdma-rnc {
      prefix "Rnc";
   }


  typedef asciiString {
    type string {
      pattern '[ -~]*';
    }
  }

       
   typedef pathString
   {
      type asciiString
      { 
         length "0..4096";    // number of bytes
      }
   } 




   


   grouping fsOperations
   {

               container results {
                  leaf-list fileList {
                     type asciiString
                     {
                        length "0..4096";
                     }
                 }
              }

  }

   grouping Fs-Mos{

      container Fs {
 
         uses fsOperations;

    }
   }


}
