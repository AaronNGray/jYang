module rbac {
	
  namespace "urn:loria:madynes:ensuite:yencap:module:RBAC:1.0";
  prefix ac;
 
 	typedef user_id {
 		type int16 {
 			range "1..max";
 		}
 	}
 	typedef name {
 		type string {
 			length "3..30";
 			pattern "([A-Z][a-z| ])*";
 		}
 	}
 	typedef login {
 		type string {
 			length "3..8";
 			pattern "[a-z]*";
 		}
 	}
 	typedef user_password {
 		type string {
 			length "8..25";
 		}
 	}
 	
 	typedef public_key {
 		type string;
 	}
 	typedef user_room {
 		type string;
 	}
 	
 	grouping user_base {
 		leaf id { type user_id;}
 		leaf login { type login;}
 		leaf password { type user_password;}
 	}
 	
 	grouping user_localization {
 		leaf firstname { type name;}
 		leaf lastname { type name;}
 		leaf room {type user_room;}
 		leaf publickey {type public_key;} 
 	}
 	
 	
 	list users {
 		key "id";
 		choice  c {
 			case minimal {
 				uses user_base;
 			}
 			case full {
 				uses user_base;
 				uses user_localization;
 			}
 		}
 	}
 	typedef role_id {
 		type int16 {
 			range "1..max";
 		}
 	}
 	
 	typedef junior_role {
 		type role_id;
 	}
 	
 	list roles {
 		key "id";
 		
 		choice c {
 		 case root {
 		 	leaf id { type role_id;}
 		 }
 		 case junior {
 		 	leaf id { type role_id;}
 		 	leaf-list juniors {
 		 		type junior_role;
 		 	}
 		 }
 		}
 	}}}
 		
}
