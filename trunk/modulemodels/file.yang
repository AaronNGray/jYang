module file {

	namespace "conf";
	prefix f;
	
	description toto;
	
	reference t  n ;
	
	
//	grouping file {
	 
		//container  file  {   
		
			list oo  { dfgh
			    leaf a { type int8;}
			 }
			//anyxml zerfger {srtg  }
		    //case c  {
			leaf name {  type string { l length 2se..-12 ;
	
	  } reference o k;  }      
			leaf rights { sfze type  string; }
			leaf owner dfsg { type string }
			leaf group   { type string; }
			//}
		//}
		
		//leaf a { type l  int8}
//	}
/*	
	leaf-list l {  type int8 }
	
	typedef t { type stridng; }
	*/
}
