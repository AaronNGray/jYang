submodule module5 {

	belongs-to module3{ prefix m3; }
	//import module3 { prefix m3; }
	
	typedef m5int {
		   type int8;
		}
	typedef m3int {
		type int8;
	}
	typedef m5int2 {
		type int8;
	}
	
	grouping g5 {
	   typedef m55 { type int8;}
	}
}
