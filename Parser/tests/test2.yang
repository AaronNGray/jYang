submodule test2 {
  belongs-to test1 {
    prefix "test1";
  }

  import test3 {
    prefix "test3";
  }

  grouping transactionIdGroup {
    leaf transactionId {
      type test3:asciiString {
        length "6..289";
      }
    }
  }
}
