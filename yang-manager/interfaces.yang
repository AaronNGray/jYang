submodule interfaces {

	belongs-to netconf { prefix net;}
	

	grouping generic-state {
	    leaf bytes {type uint64;}
	    leaf packets { type uint64;}
	    leaf drop { type uint64;}
	    leaf compressed {type uint64;}
	    leaf fifo { type uint64;}
	    leaf errs {type uint64;}
	}
		
	grouping interface {
		list interface {
			key name;
			leaf name { type string;}
			leaf mac-address { type string;
								default "000000000000";
								mandatory false;}
			leaf mtu { type uint32;}
			container ipv4 {
				leaf netmask { type string;}
				leaf broadcast {type string;}
				leaf address-v4 {type string;}
			}
			container stats {
				container received { uses generic-state;}
				container transmit { uses generic-state;}
			}
		}
		  
	}
}
