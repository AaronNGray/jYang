module m1 {
	
  namespace "www";
  prefix p1;
 
  import m2 { prefix p2;}

  //typedef t1 { type int8;}
  //typedef t2 { type p2:t12;}
  
  grouping g1 {
    leaf l1 { type int8;}
  }
  container c1 {
  	uses g1;
  	leaf l2 { type int8;}
  }
}
