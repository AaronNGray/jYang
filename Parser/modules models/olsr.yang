module OLRS {

	namespace "urn:loria:madynes:ensuite:olsr:1.0";
	prefix olsr;
	
	import ietf-inet-types {prefix dinet;}
	
	leaf debugLevel {
		type int8;
		default 0;
		description "Controls the amount of debug output olsrd sends to stdout. 
					If set to 0, olsrd will detatch from the current process and run in 
					the background. A value of 9 yields a maximum of debug output.";
	}
	
	leaf linkQualityFishEye {
		type enumeration { enum off { value 0;}
						   enum on { value 1;}
		}
		description "Fisheye mechanism for TC messages 0=off, 1=on";
	}
	
	leaf dijkstraLimit {
		type int8;
		description "ignore topology information from nodes further than n hops away";
	}
	
	leaf linkQuality{
		type float32 { range "0..max";}
		description "update topology information every 3.0 seconds                  
				     on slower embedded hardware with more than 100 nodes 
				     use something like 9 sec";
	}

	leaf ipVersion {
		type int8;
		default 4;
		description "Olsrd supports both IP version 4 and 6. 
				This option controls what IP version olsrd is to use. 
				Defaults to 4.";
	}
	
	leaf clearScreen {
		type string { length "2..3";
					  pattern "yes|no";
		}
		default "yes";
		description "If set to yes and olsrd is running with a debuglevel >0 the terminal to which
					output is sent(STDOUT) is cleared prior to writing updated tables. This makes it easier to follow 
					changes in real-time by eye. If STDOUT is not a terminal(eg. it is a file), then no action is 
					taken upon writing tables to STDOUT. ";
	}
		
	leaf willingness {
		type int8 { range "0..7";}
		default 4;
		description "Nodes participating in a OLSR routed network will announce their willingness
			 to act as relays for OLSR control traffic for their neighbors. This option specifies a 
			 fixed willingness value to be announced by the local node. 4 is a neutral option here, 
			 while 0 specifies that this node will never act as a relay, and 7 specifies that this node 
			 will always act as such a relay. If this option is not set in the configuration file, then 
			 olsrd will try to retrieve information about the system power and dynamically update willingness
			  according to this info. If no such info can be retrieved willingness is set to 4.";
	}
	
	leaf allowNoInt {
		type string { pattern "yes|no";}
		default "yes";
		description "Olsrd supports dynamic configuration of network interfaces. This means that 
					interfaces on which olsrd runs, can be reconfigured and olsrd will update itself
					 with no need to be restarted. Olsrd also supports removal and addittion of interfaces
					  in run-time. This option specifies if olsrd should keep running if no network 
					  interfaces are available. Defaults to yes.";
	}
	
	leaf tosValue {
		type int8 { range "0..16";}
		default 16;
    	description "This value controls the type of service value to set in the IP header 
    			of OLSR control traffic. Defaults to 16.";
    } 
    
    leaf useHysteresis {
    	type string { pattern "yes|no";}
    	default yes;
    	description "If set to yes hysteresis will be used as explained in section 14 of RFC3626."; 
    }
    
    leaf hystScaling {
    	type float32 { range "0.01..0.99";}
    	default "0.5";
    	description "Sets the scaling value used by the hysteresis algorithm. This must be a positive 
    				floating point value smaller than 1.0. Consult RFC3626 for details. The default 
    				value is 0.5.";
    }
    
	leaf hystThrHigh {
		type float32 { range "0..0.99";}
		default 0.8;
		must "hystThrLow < this";
		description "This option sets the upper threshold for accepting a link in hysteresis calculation. 
					The value must be higher than the one set as the lower threshold. Defaults to 0.8.";
	}
	
	leaf hystThrLow {
		type float32 { range "0.01..0.99";}
		default 0.3;
		must "hystThrHigh > this";
		description "This option sets the lower threshold for setting a link to asymmetric using hysteresis. 
					 The value must be lower than the one set as the upper threshold. Defaults to 0.3."; 
	}
	
	leaf linkQualityLevel {
			type int8 { range "0..2";}
			default 0;
			description 'This setting decides the Link Quality scheme to use. If set to 0 link quality
					 is not regarded and olsrd runs in "RFC3626 mode". If set to 1 link quality is used 
					 when calculating MPRs. If set to 2 routes will also be calculated based on 
					 distributed link quality information. Note that a setting of 1 or 2 breaks RFC3626 compability! 
					 This option should therefore only be set to 1 or 2 if such a setting is used by 
					 all other nodes in the network.';
	} 
	
	leaf pollrate { 
			type float32 { range "0..INF";}
			default "0.1";
			description "This option sets the interval, in seconds, that the olsrd event scheduler should be set 
			to poll. A setting of 0.2 will set olsrd to poll for events every 0.2 seconds. Defaults to 0.1.";
	}
	
	leaf tcRedundancy {
		type int8 { range "0..2";}
		default 0;
		description "This value controls the TC redundancy used by the local node in TC message generation. 
					To enable a more robust understanding of the topology, nodes can be set to announce more 
					than just their MPR selector set in TC messages. If set to 0 the advertised link set of
					the node is limited to the MPR selectors. If set to 1 the advertised link set of the node 
					is the union of its MPR set and its MPR selector set. Finally, if set to 2 the advertised 
					link set of the node is the full symmetric neighbor set of the node. Defaults to 0.";
	}
	
	leaf mprCoverage {
		type int8 { range "1..max";}
		default 1;
		description "This value decides how many MPRs a node should attempt to select for every two hop neighbor. 
					Defaults to 1 , and any other setting will severly reduce the optimization introduced
					 by the MPR secheme!";
	}
	
	container interfaces {
	
		list interface {
	
			key name;
			
			leaf name {
				type string;
			}
			
			leaf ip4Broadcast {
				type dinet:ipv4-address;
			}
			
			leaf ip6AddrType {
				type string { pattern "site-local|global";}
				default "site-local";
			}
			
			leaf ip6MulticastSite {
				type dinet:ipv6-address;
				description "Sets the destionation of outgoing OLSR traffic on 
							this interface to use the specified IPv6 multicast address as 
							destination if the site-local address type is set on this interface.";
			}
			
			leaf ip6MulticastGlobal  {
				type dinet:ipv6-address;
				description "Sets the destionation of outgoing OLSR traffic on this interface to use 
							the specified IPv6 multicast address as destination if the global address
							type is set on this interface.";
			}
			 
			leaf helloInterval {
				type float32 {range "0.0..INF";}
				description "Sets the interval on which HELLO messages will be 
				generated and transmitted on this interface.";
			} 
			
			leaf helloValidityTime {
				type float32 {range "0.0..INF";}
				description "Sets the validity time to be announced in HELLO messages
						generated by this host on this interface. This value must be larger 
						than the HELLO generation interval to make any sense. 
						Defaults to 3 * the generation interval.";
			}
			
			leaf TcInterval {
				type float32 {range "0.0..INF";}
				description "Sets the interval on which TC messages will 
							be generated and transmitted on this interface.";
			}

			leaf tcValidityTime {
				type float32 {range "0.0..INF";}
				description "Sets the validity time to be announced in TC messages generated by 
						this host on this interface. This value must be larger than than the TC
						generation interval to make any sense. Defaults to 3 * the generation interval.";
			}

			leaf midInterval {
				type float32 {range "0.0..INF";}
				description "Sets the interval on which MID messages will be generated and 
							transmitted on this interface.";
			}

			leaf midValidityTime {
				type float32 {range "0.0..INF";}
				description "Sets the validity time to be announced in MID messages generated 
							 by this host on this interface. This value must be larger than 
							 than the MID generation interval to make any sense. 
							 Defaults to 3 * the generation interval.";
			}

			leaf hnaInterval {
				type float32 {range "0.0..INF";}
				description "Sets the interval on which HNA messages will be generated and 
							transmitted on this interface.";
			}

			leaf hnaValidityTime {
				type float32 {range "0.0..INF";}
				description "Sets the validity time to be announced in HNA messages 
							 generated by this host on this interface. This value must be 
							 larger than than the HNA generation interval to make any sense. 
							 Defaults to 3 * the generation interval.";
			}

			leaf weight {
				type int32 {range "0..max";}
				description "When multiple links exist between hosts the weight of the 
				interface is used to determine the link to route by. Normally the weight is 
				automatically calculated by olsrd based on the characteristics of the interface, 
				but here you can specify a fixed value. Olsrd will choose links with the lowest value.";
			} 
			
		}
	}
			
			
	
	
}
