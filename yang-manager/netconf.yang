module netconf {

	namespace "urn:loria:madynes:ensuite:yencap:1.0";
	prefix ycp;
	
	include network;
	include security;
	
	
	container netconf {
		container network { uses network; }
		container security { uses security;}
	}
	
}
